VARNISH-MIB DEFINITIONS ::= BEGIN

-- *************************************************************
-- $Id: VARNISH-MIB.txt 8 2014-11-24 14:38:24Z graygnuorg $
--
-- Varnish reverse proxy MIB
-- by Shared Autonomous sYstems
--
-- *************************************************************

IMPORTS
	MODULE-IDENTITY, OBJECT-TYPE, enterprises, Counter64, TimeTicks,
	Counter32, Integer32
		FROM SNMPv2-SMI
	TEXTUAL-CONVENTION, DateAndTime
		FROM SNMPv2-TC
	InetAddressIPv4, InetAddressIPv6, InetPortNumber
		FROM INET-ADDRESS-MIB
	OBJECT-GROUP, MODULE-COMPLIANCE
		FROM SNMPv2-CONF;

varnishMIB MODULE-IDENTITY
	LAST-UPDATED "201509250838Z"
	ORGANIZATION "Shared Autonomous sYstems"
	CONTACT-INFO "Morten Hermanrud <mhe@say.no>
	              Sergey Poznyakoff <gray@gnu.org>
		     "
	DESCRIPTION 
		"This MIB module defines objects for Varnish reverse web proxy."
	REVISION "201509250838Z"
	DESCRIPTION 
		"Second revision."
	::= { varnish 0 }

varnish OBJECT IDENTIFIER	::= { enterprises 33043 6 1 }
client  OBJECT IDENTIFIER	::= { varnish 1 }
backend OBJECT IDENTIFIER	::= { varnish 2 }
total   OBJECT IDENTIFIER	::= { varnish 3 }
master	OBJECT IDENTIFIER	::= { varnish 4 }
session	OBJECT IDENTIFIER	::= { varnish 5 }
threads	OBJECT IDENTIFIER	::= { varnish 6 }
bans	OBJECT IDENTIFIER	::= { varnish 7 }
agent	OBJECT IDENTIFIER	::= { varnish 8 }

clientAcceptedConnections OBJECT-TYPE
	SYNTAX  Counter64
	MAX-ACCESS read-only
	STATUS  current
	DESCRIPTION
		"Client connections accepted."
	::= { client 1 }

clientRequestsReceived OBJECT-TYPE
	SYNTAX  Counter64
	MAX-ACCESS read-only
	STATUS  current
	DESCRIPTION
		"Client requests received."
	::= { client 2 }

clientCacheHits OBJECT-TYPE
	SYNTAX  Counter64
	MAX-ACCESS read-only
	STATUS  current
	DESCRIPTION
		"Cache hits."
	::= { client 3 }

clientCacheHitsPass OBJECT-TYPE
	SYNTAX  Counter64
	MAX-ACCESS read-only
	STATUS  current
	DESCRIPTION
		"Cache hits for pass."
	::= { client 4 }

clientCacheMisses OBJECT-TYPE
	SYNTAX  Counter64
	MAX-ACCESS read-only
	STATUS  current
	DESCRIPTION
		"Cache misses."
	::= { client 5 }

VarnishBanString ::= TEXTUAL-CONVENTION
    DISPLAY-HINT "1024t"
    STATUS       current
    DESCRIPTION "A string containing Varnish ban expression."
    SYNTAX       OCTET STRING (SIZE (0..1024))
       	
clientBan OBJECT-TYPE
	SYNTAX	VarnishBanString
	MAX-ACCESS  read-write
	STATUS      current
	DESCRIPTION
		"When set, invalidates the cache using the supplied value as
		 argument to ban.  When read, returns an empty string."
	::= { client 6 }

clientRequests400 OBJECT-TYPE
	SYNTAX  Counter64
	MAX-ACCESS read-only
	STATUS  current
	DESCRIPTION
		"Client requests received, subject to 400 errors."
	::= { client 7 }

clientRequests411 OBJECT-TYPE
	SYNTAX  Counter64
	MAX-ACCESS read-only
	STATUS  current
	DESCRIPTION
		"Client requests received, subject to 411 errors."
	::= { client 8 }

clientRequests413 OBJECT-TYPE
	SYNTAX  Counter64
	MAX-ACCESS read-only
	STATUS  current
	DESCRIPTION
		"Client requests received, subject to 413 errors."
	::= { client 9 }

clientRequests417 OBJECT-TYPE
	SYNTAX  Counter64
	MAX-ACCESS read-only
	STATUS  current
	DESCRIPTION
		"Client requests received, subject to 417 errors."
	::= { client 10 }
	
connections OBJECT IDENTIFIER    ::= { backend 1 }

backendConnSuccess OBJECT-TYPE
	SYNTAX  Counter64
	MAX-ACCESS read-only
	STATUS  current
	DESCRIPTION
		"Backend connections success."
	::= { connections 1 }
 
backendConnNotAttempted OBJECT-TYPE
	SYNTAX  Counter64
	MAX-ACCESS read-only
	STATUS  current
	DESCRIPTION
		"Backend connections not attempted."
	::= { connections 2 }
 
backendConnToMany OBJECT-TYPE
	SYNTAX  Counter64
	MAX-ACCESS read-only
	STATUS  current
	DESCRIPTION
		"Backend connections too many."
	::= { connections 3 }
 
backendConnFailures OBJECT-TYPE
	SYNTAX  Counter64
	MAX-ACCESS read-only
	STATUS  current
	DESCRIPTION
		"Backend connections failures."
	::= { connections 4 }
 
backendConnReuses OBJECT-TYPE
	SYNTAX  Counter64
	MAX-ACCESS read-only
	STATUS  current
	DESCRIPTION
		"Backend connections reuses."
	::= { connections 5 }
 
backendConnRecycled OBJECT-TYPE
	SYNTAX  Counter64
	MAX-ACCESS read-only
	STATUS  current
	DESCRIPTION
		"Backend connections recycles."
	::= { connections 6 }
 
backendConnUnused OBJECT-TYPE
	SYNTAX  Counter64
	MAX-ACCESS read-only
	STATUS  current
	DESCRIPTION
		"Backend connections unused."
	::= { connections 7 }

backendConnRetry OBJECT-TYPE
	SYNTAX  Counter64
	MAX-ACCESS read-only
	STATUS  current
	DESCRIPTION
		"Backend connections retried."
	::= { connections 8 }

backendRequests OBJECT-TYPE
	SYNTAX  Counter64
	MAX-ACCESS read-only
	STATUS  current
	DESCRIPTION
		"Total backend requests made."
	::= { backend 2 }

backendTable OBJECT-TYPE
	SYNTAX	SEQUENCE OF VarnishBackendEntry
	MAX-ACCESS not-accessible
	STATUS	current
	DESCRIPTION
		"A table of configured backends and their statistics"
	::= { backend 3 }

varnishBackendEntry OBJECT-TYPE
	SYNTAX	VarnishBackendEntry
	MAX-ACCESS not-accessible
	STATUS	current
	DESCRIPTION
		"An entry (conceptual row) describing a backend."
	INDEX	{ vbeIndex }
	::= { backendTable 1 }

VarnishBackendIdentString ::= TEXTUAL-CONVENTION
    DISPLAY-HINT "256t"
    STATUS       current
    DESCRIPTION "An identifier of a Varnish backend."
    SYNTAX       OCTET STRING (SIZE (0..256))
	
VarnishBackendEntry ::= SEQUENCE {
	vbeIndex		Integer32,
	vbeIdent		VarnishBackendIdentString,
	vbeIPv4                 InetAddressIPv4,
	vbeIPv6                 InetAddressIPv6,
	vbePort			InetPortNumber,
	vbeHappyProbes		Counter64,
	vbeVcls	                Counter64,
	vbeRequestHeaderBytes	Counter64,
	vbeRequestBodyBytes	Counter64,
	vbeResponseHeaderBytes	Counter64,
	vbeResponseBodyBytes	Counter64,
	vbePipeHeaderBytes	Counter64,
	vbePipeIn		Counter64,
	vbePipeOut		Counter64
}

vbeIndex OBJECT-TYPE
	SYNTAX  Integer32 (0..65535)
	MAX-ACCESS not-accessible
	STATUS  current
	DESCRIPTION
		"A number uniquely identifying each backend."
	::= { varnishBackendEntry 1 }

vbeIdent OBJECT-TYPE
	SYNTAX  VarnishBackendIdentString
	MAX-ACCESS read-only
	STATUS  current
	DESCRIPTION
		"Textual identifier of the backend."
	::= { varnishBackendEntry 2 }

vbeIPv4 OBJECT-TYPE
	SYNTAX  InetAddressIPv4
	MAX-ACCESS read-only
	STATUS  current
	DESCRIPTION
		"IPv4 address of the backend.  Empty if the backend has no
		 IPv4 address."
	::= { varnishBackendEntry 3 }
                 
vbeIPv6 OBJECT-TYPE
	SYNTAX InetAddressIPv6 
	MAX-ACCESS read-only
	STATUS  current
	DESCRIPTION
		"IPv6 address of the backend.  Empty if the backend has no
		 IPv6 address."
	::= { varnishBackendEntry 4 }
                 
vbePort OBJECT-TYPE
	SYNTAX  InetPortNumber
	MAX-ACCESS read-only
	STATUS  current
	DESCRIPTION
		"Port number."
	::= { varnishBackendEntry 5 }
	
vbeHappyProbes OBJECT-TYPE
	SYNTAX  Counter64
	MAX-ACCESS read-only
	STATUS  current
	DESCRIPTION
		"Number of successful health probes."
	::= { varnishBackendEntry 6 }
		
vbeVcls OBJECT-TYPE
	SYNTAX  Counter64
	MAX-ACCESS read-only
	STATUS  current
	DESCRIPTION
		"Number of VCL references."
	::= { varnishBackendEntry 7 }

vbeRequestHeaderBytes OBJECT-TYPE
	SYNTAX  Counter64
	MAX-ACCESS read-only
	STATUS  current
	DESCRIPTION
		"Total number of request header bytes sent to that backend."
	::= { varnishBackendEntry 8 }
	
vbeRequestBodyBytes OBJECT-TYPE
	SYNTAX  Counter64
	MAX-ACCESS read-only
	STATUS  current
	DESCRIPTION
		"Total number of request body bytes sent to that backend."
	::= { varnishBackendEntry 9 }
	
vbeResponseHeaderBytes OBJECT-TYPE
	SYNTAX  Counter64
	MAX-ACCESS read-only
	STATUS  current
	DESCRIPTION
		"Total number of response header bytes received from that backend."
	::= { varnishBackendEntry 10 }
	
vbeResponseBodyBytes OBJECT-TYPE
	SYNTAX  Counter64
	MAX-ACCESS read-only
	STATUS  current
	DESCRIPTION
		"Total number of response body bytes received from that backend."
	::= { varnishBackendEntry 11 }
	
vbePipeHeaderBytes OBJECT-TYPE
	SYNTAX  Counter64
	MAX-ACCESS read-only
	STATUS  current
	DESCRIPTION
		"Total number of header bytes piped to that backend."
	::= { varnishBackendEntry 12 }
	
vbePipeIn OBJECT-TYPE
	SYNTAX  Counter64
	MAX-ACCESS read-only
	STATUS  current
	DESCRIPTION
		"Total number of bytes piped to that backend."
	::= { varnishBackendEntry 13 }
		
vbePipeOut OBJECT-TYPE
	SYNTAX  Counter64
	MAX-ACCESS read-only
	STATUS  current
	DESCRIPTION
		"Total number of bytes piped from that backend."
	::= { varnishBackendEntry 14 }
	
totalSessions OBJECT-TYPE
	SYNTAX  Counter64
	MAX-ACCESS read-only
	STATUS  current
	DESCRIPTION
		"Total Sessions."
	::= { total 1 }
 
totalRequests OBJECT-TYPE
	SYNTAX  Counter64
	MAX-ACCESS read-only
	STATUS  current
	DESCRIPTION
		"Total Requests."
	::= { total 2 }
 
totalPipe OBJECT-TYPE
	SYNTAX  Counter64
	MAX-ACCESS read-only
	STATUS  current
	DESCRIPTION
		"Total pipe."
	::= { total 3 }
 
totalPass OBJECT-TYPE
	SYNTAX  Counter64
	MAX-ACCESS read-only
	STATUS  current
	DESCRIPTION
		"Total pass."
	::= { total 4 }
 
totalFetch OBJECT-TYPE
	SYNTAX  Counter64
	MAX-ACCESS read-only
	STATUS  current
	DESCRIPTION
		"Total fetch."
	::= { total 5 }
 
totalRequestHeaderBytes OBJECT-TYPE
	SYNTAX  Counter64
	MAX-ACCESS read-only
	STATUS  current
	DESCRIPTION
		"Total request header bytes."
	::= { total 6 }
 
totalRequestBodyBytes OBJECT-TYPE
	SYNTAX  Counter64
	MAX-ACCESS read-only
	STATUS  current
	DESCRIPTION
		"Total request body bytes."
	::= { total 7 }

totalResponseHeaderBytes OBJECT-TYPE
	SYNTAX  Counter64
	MAX-ACCESS read-only
	STATUS  current
	DESCRIPTION
		"Total response body bytes."
	::= { total 8 }
	
totalResponseBodyBytes OBJECT-TYPE
	SYNTAX  Counter64
	MAX-ACCESS read-only
	STATUS  current
	DESCRIPTION
		"Total response body bytes."
	::= { total 9 }

totalPipeHeaderBytes OBJECT-TYPE
	SYNTAX  Counter64
	MAX-ACCESS read-only
	STATUS  current
	DESCRIPTION
		"Total request header bytes received for piped sessions."
	::= { total 10 }
	
totalPipeIn OBJECT-TYPE
	SYNTAX  Counter64
	MAX-ACCESS read-only
	STATUS  current
	DESCRIPTION
		"Total number of bytes forwarded from clients in pipe sessions."
	::= { total 11 }
	
totalPipeOut OBJECT-TYPE
	SYNTAX  Counter64
	MAX-ACCESS read-only
	STATUS  current
	DESCRIPTION
		"Total number of bytes forwarded to clients in pipe sessions."
	::= { total 12 }
	
uptime OBJECT-TYPE
	SYNTAX	TimeTicks
	MAX-ACCESS read-only
	STATUS  current
	DESCRIPTION
		"Master daemon uptime."
	::= { master 1 }	

sessAccepted OBJECT-TYPE
	SYNTAX  Counter64
	MAX-ACCESS read-only
	STATUS  current
	DESCRIPTION
		"Number of sessions succesfully accepted."
	::= { session 1 }

sessQueued OBJECT-TYPE
	SYNTAX  Counter64
	MAX-ACCESS read-only
	STATUS  current
	DESCRIPTION
		"Number of times session was queued waiting for a thread."
	::= { session 2 }

sessDropped OBJECT-TYPE
	SYNTAX  Counter64
	MAX-ACCESS read-only
	STATUS  current
	DESCRIPTION
		"Number of sessions dropped because session queue was full."
	::= { session 3 }

sessClosed OBJECT-TYPE
	SYNTAX  Counter64
	MAX-ACCESS read-only
	STATUS  current
	DESCRIPTION
		"Number of sessions closed."
	::= { session 4 }

sessPipeline OBJECT-TYPE
	SYNTAX  Counter64
	MAX-ACCESS read-only
	STATUS  current
	DESCRIPTION
		"Session pipeline."
	::= { session 5 }

sessReadAhead OBJECT-TYPE
	SYNTAX  Counter64
	MAX-ACCESS read-only
	STATUS  current
	DESCRIPTION
		"Session read-ahead."
	::= { session 6 }

sessHerd OBJECT-TYPE
	SYNTAX  Counter64
	MAX-ACCESS read-only
	STATUS  current
	DESCRIPTION
		"Session herd."
	::= { session 7 }	
		
sessDrop OBJECT-TYPE
	SYNTAX  Counter64
	MAX-ACCESS read-only
	STATUS  current
	DESCRIPTION
		"Number of sessions dropped for thread."
	::= { session 8 }	

sessFail OBJECT-TYPE
	SYNTAX  Counter64
	MAX-ACCESS read-only
	STATUS  current
	DESCRIPTION
		"Number of session accept failures."
	::= { session 9 }	

sessPipeOverflow OBJECT-TYPE
	SYNTAX  Counter64
	MAX-ACCESS read-only
	STATUS  current
	DESCRIPTION
		"Number of session pipe overflows."
	::= { session 10 }	

threadsPools OBJECT-TYPE
	SYNTAX  Counter64
	MAX-ACCESS read-only
	STATUS  current
	DESCRIPTION
		"Number of thread pools."
	::= { threads 1 }	

threadsTotal OBJECT-TYPE
	SYNTAX  Counter64
	MAX-ACCESS read-only
	STATUS  current
	DESCRIPTION
		"Number of thread pools."
	::= { threads 2 }	

threadsLimitHits OBJECT-TYPE
	SYNTAX  Counter64
	MAX-ACCESS read-only
	STATUS  current
	DESCRIPTION
		"Number of times more threads were needed, but limit was
		 reached in a thread pool."
	::= { threads 3 }	

threadsCreated OBJECT-TYPE
	SYNTAX  Counter64
	MAX-ACCESS read-only
	STATUS  current
	DESCRIPTION
		"Total number of threads created in all pools."
	::= { threads 4 }	

threadsDestroyed OBJECT-TYPE
	SYNTAX  Counter64
	MAX-ACCESS read-only
	STATUS  current
	DESCRIPTION
		"Total number of threads destroyed in all pools."
	::= { threads 5 }	

threadsFailed OBJECT-TYPE
	SYNTAX  Counter64
	MAX-ACCESS read-only
	STATUS  current
	DESCRIPTION
		"Number of times creating a thread failed."
	::= { threads 6 }	

threadsQueueLength OBJECT-TYPE
	SYNTAX  Counter64
	MAX-ACCESS read-only
	STATUS  current
	DESCRIPTION
		"Length of session queue waiting for threads."
	::= { threads 7 }
	
bansTotal OBJECT-TYPE
	SYNTAX  Counter64
	MAX-ACCESS read-only
	STATUS  current
	DESCRIPTION
		"Total number of bans."
	::= { bans 1 }

bansCompleted OBJECT-TYPE
	SYNTAX  Counter64
	MAX-ACCESS read-only
	STATUS  current
	DESCRIPTION
		"Count of completed bans."
	::= { bans 2 }

bansObj OBJECT-TYPE
	SYNTAX  Counter64
	MAX-ACCESS read-only
	STATUS  current
	DESCRIPTION
		"Number of bans using obj.*."
	::= { bans 3 }

bansReq OBJECT-TYPE
	SYNTAX  Counter64
	MAX-ACCESS read-only
	STATUS  current
	DESCRIPTION
		"Number of bans using req.*."
	::= { bans 4 }

bansAdded OBJECT-TYPE
	SYNTAX  Counter64
	MAX-ACCESS read-only
	STATUS  current
	DESCRIPTION
		"Number of bans added."
	::= { bans 5 }

bansDeleted OBJECT-TYPE
	SYNTAX  Counter64
	MAX-ACCESS read-only
	STATUS  current
	DESCRIPTION
		"Number of bans deleted."
	::= { bans 6 }

bansTested OBJECT-TYPE
	SYNTAX  Counter64
	MAX-ACCESS read-only
	STATUS  current
	DESCRIPTION
		"Number of bans tested against objects (lookup)."
	::= { bans 7 }

bansObjectsKilled OBJECT-TYPE
	SYNTAX  Counter64
	MAX-ACCESS read-only
	STATUS  current
	DESCRIPTION
		"Number of objects killed by bans (lookup)."
	::= { bans 8 }


bansLurkerTested OBJECT-TYPE
	SYNTAX  Counter64
	MAX-ACCESS read-only
	STATUS  current
	DESCRIPTION
		"Number of bans tested against objects (lurker)."
	::= { bans 9 }

bansTestTested OBJECT-TYPE
	SYNTAX  Counter64
	MAX-ACCESS read-only
	STATUS  current
	DESCRIPTION
		"Number of ban tests tested against objects (lookup)."
	::= { bans 10 }

bansLurkerTestTested OBJECT-TYPE
	SYNTAX  Counter64
	MAX-ACCESS read-only
	STATUS  current
	DESCRIPTION
		"Number of ban tests tested against objects (lurker)."
	::= { bans 11 }

bansLurkerObjKilled OBJECT-TYPE
	SYNTAX  Counter64
	MAX-ACCESS read-only
	STATUS  current
	DESCRIPTION
		"Number of objects killed by bans (lurker)."
	::= { bans 12 }

bansDups OBJECT-TYPE
	SYNTAX  Counter64
	MAX-ACCESS read-only
	STATUS  current
	DESCRIPTION
		"Number of ans superseded by other bans."
	::= { bans 13 }

bansLurkerContention OBJECT-TYPE
	SYNTAX  Counter64
	MAX-ACCESS read-only
	STATUS  current
	DESCRIPTION
		"Number of times lurker gave way for lookup."
	::= { bans 14 }

bansPersistedBytes OBJECT-TYPE
	SYNTAX  Counter64
	MAX-ACCESS read-only
	STATUS  current
	DESCRIPTION
		"Number of bytes used by the persisted ban lists."
	::= { bans 15 }

bansPersistedFragmentation OBJECT-TYPE
	SYNTAX  Counter64
	MAX-ACCESS read-only
	STATUS  current
	DESCRIPTION
		"Extra bytes in persisted ban lists due to fragmentation."
	::= { bans 17 }

banTable OBJECT-TYPE
       SYNTAX     SEQUENCE OF VarnishBanEntry
       MAX-ACCESS not-accessible
       STATUS     current
       DESCRIPTION
             "The (conceptual) table listing available bans."
       ::= { bans 18 }

varnishBanEntry OBJECT-TYPE
       SYNTAX     VarnishBanEntry
       MAX-ACCESS not-accessible
       STATUS     current
       DESCRIPTION
             "An entry (conceptual row) representing a ban."
       INDEX      { banIndex }
       ::= { banTable 1 }

VarnishBanEntry ::= SEQUENCE {
       banIndex                           Integer32,
       banTime				  DateAndTime,
       banRefCount                        Counter32,
       banExpression			  VarnishBanString
}

banIndex OBJECT-TYPE
	SYNTAX  Integer32 (0..65535)
	MAX-ACCESS not-accessible
	STATUS  current
	DESCRIPTION
		"A number uniquely identifying each ban."
	::= { varnishBanEntry 1 }

banTime OBJECT-TYPE
	SYNTAX  DateAndTime
	MAX-ACCESS read-only
	STATUS  current
	DESCRIPTION
		"Time when the ban was created."
	::= { varnishBanEntry 2 }

banRefCount OBJECT-TYPE
	SYNTAX  Counter32
	MAX-ACCESS read-only
	STATUS  current
	DESCRIPTION
		"Number of references to this ban."
	::= { varnishBanEntry 3 }
	
banExpression OBJECT-TYPE
	SYNTAX  VarnishBanString
	MAX-ACCESS read-only
	STATUS  current
	DESCRIPTION
		"VCL expression of the ban."
	::= { varnishBanEntry 4 }

--
-- Groups and Compliance
--
varnishConfs  OBJECT IDENTIFIER	::= { varnish 100 }
varnishGroups OBJECT IDENTIFIER	::= { varnishConfs 1 }
varnishCompl  OBJECT IDENTIFIER ::= { varnishConfs 2 }

--
-- Groups
--
varnishGroup OBJECT-GROUP
	OBJECTS {
                clientAcceptedConnections,
		clientRequestsReceived,
		clientCacheHits,
		clientCacheHitsPass,
		clientCacheMisses,
		clientBan,
		backendConnSuccess,
		backendConnNotAttempted,
		backendConnToMany,
		backendConnFailures,
		backendConnReuses,
		backendConnRecycled,
		backendConnUnused,
		backendConnRetry,
		backendRequests,
		vbeIPv4,
		vbeIPv6,
		vbePort,
		vbeHappyProbes,
		vbeVcls,
		vbeRequestHeaderBytes,
		vbeRequestBodyBytes,
		vbeResponseHeaderBytes,
		vbeResponseBodyBytes,
		vbePipeHeaderBytes,
		vbePipeIn,
		vbePipeOut,
		totalSessions,
		totalRequests,
		totalPipe,
		totalPass,
		totalFetch,
		clientRequests400,
		clientRequests411,
		clientRequests413,
		clientRequests417,
		totalRequestHeaderBytes,
		totalRequestBodyBytes,
		totalResponseHeaderBytes,
		totalResponseBodyBytes,
		totalPipeHeaderBytes,
		totalPipeIn,
		totalPipeOut,
		uptime,
		sessAccepted,
		sessQueued,
		sessDropped, 
		sessClosed,
		sessPipeline,
		sessReadAhead,
		sessHerd,
		sessDrop,
		sessFail,
		sessPipeOverflow,
		threadsPools,
		threadsTotal,
		threadsLimitHits,
		threadsCreated,
		threadsDestroyed,
		threadsFailed,
		threadsQueueLength,
		banTime,
		banRefCount,
		banExpression
		}

	STATUS  current
	DESCRIPTION "Group of Varnish objects."
	::= { varnishGroups 1 }

--
-- Compliance
--
varnishStandardComplianceV1 MODULE-COMPLIANCE
	STATUS  current
	DESCRIPTION
		"Compliance for a Varnish agent."

	MODULE 
	MANDATORY-GROUPS { varnishGroup }

	::= { varnishCompl 1 }

END

-- Local variables:
-- eval: (add-hook 'write-file-hooks 'time-stamp)
-- time-stamp-start: "\\(LAST-UPDATED\\|REVISION\\)  *\""
-- time-stamp-end: "\""
-- time-stamp-format: "%:y%02m%02d%02H%02MZ"
-- time-stamp-line-limit: 32
-- time-stamp-count: 2
-- end:
